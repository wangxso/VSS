BASE DEFINITIONS AUTOMATIC TAGS ::= BEGIN
    
EXPORTS ALL;

Uint3  ::= INTEGER (0..7)                    -- (hex)                      07
Uint8  ::= INTEGER (0..255)                  -- (hex)                      ff
Uint16 ::= INTEGER (0..65535)                -- (hex)                   ff ff
Uint32 ::= INTEGER (0..4294967295)		       -- (hex)             ff ff ff ff
Uint64 ::= INTEGER (0..18446744073709551615) -- (hex) ff ff ff ff ff ff ff ff

Opaque ::= OCTET STRING
HashedId8 ::= OCTET STRING (SIZE(8))
HashedId3 ::= OCTET STRING (SIZE(3))

Time32 ::= Uint32
Time64 ::= Uint64

GeographicRegion ::= CHOICE {
	circularRegion      CircularRegion,
	rectangularRegion   SequenceOfRectangularRegion,
	polygonalRegion     PolygonalRegion,
	...
}

CircularRegion ::= SEQUENCE{
	center          TwoDLocation,
	radius          Uint16
}

RectangularRegion ::= SEQUENCE{
	northWest       TwoDLocation,
	southEast       TwoDLocation
}

SequenceOfRectangularRegion ::= SEQUENCE OF RectangularRegion

PolygonalRegion ::= SEQUENCE SIZE(3..MAX) OF TwoDLocation

TwoDLocation ::= SEQUENCE {
	latitude      Latitude,
	longitude     Longitude
}

ThreeDLocation ::= SEQUENCE {
	latitude        Latitude,
	longitude       Longitude,
	elevation       Elevation
}

Latitude ::= NinetyDegreeInt

Longitude ::= OneEightyDegreeInt

Elevation ::= Uint16

NinetyDegreeInt ::= INTEGER {
	min 		(-900000000),
	max 		(900000000),
	unknown 	(900000001)
} (-900000000..900000001)

KnownLatitude ::= NinetyDegreeInt (min..max) 

UnknownLatitude ::= NinetyDegreeInt (unknown)

OneEightyDegreeInt ::= INTEGER {
	min      	(-1799999999),
	max      	(1800000000),
	unknown  	(1800000001)
} (-1799999999..1800000001)

KnownLongitude ::= OneEightyDegreeInt (min..max)
UnknownLongitude ::= OneEightyDegreeInt (unknown)

EccCurve ::= ENUMERATED {
	sgdsm2,
	nistP256,
	brainpoolP256r1,
	...
}

ECCPoint ::= CHOICE {
	x-only           OCTET STRING (SIZE (32)),
	fill             NULL,  -- consistency with 1363 / X9.62
	compressed-y-0   OCTET STRING (SIZE (32)),
	compressed-y-1   OCTET STRING (SIZE (32)),
	uncompressedP256 SEQUENCE  {
		x OCTET STRING (SIZE (32)),
		y OCTET STRING (SIZE (32))
	}
}

Signature ::= SEQUENCE {
	curve EccCurve,
	r     ECCPoint,
	s     OCTET STRING (SIZE (32))
}

HashAlgorithm ::= ENUMERATED { 
	sgdsm3,
	sha256,
	sha3-256,
	...
}

SymmetricAlgorithm ::= ENUMERATED { 
	sgdsm4ecb,
	sgdsm4cbc,
	sgdsm4cfb,
	sgdsm4ofb,
	aes128ccm,
	...
}

PublicEncryptionKey ::= SEQUENCE { 
	supportedSymmAlg      SymmetricAlgorithm,
	eccCurve              EccCurve,
	publicKey             ECCPoint
}

CertificateDigest ::= SEQUENCE {
	algorithm    	HashAlgorithm,
	digest 		    HashedId8
}

PublicVerifyKey ::= SEQUENCE {
	curve		EccCurve,
	key		ECCPoint,
	...
}

ItsAid ::= Uint64
ItsAidSsp ::= SEQUENCE {
	itsAid	 ItsAid,
	serviceSpecificPermissions  OCTET STRING (SIZE (1..32))
}
SubjectAssurance ::= OCTET STRING (SIZE (1))
SequenceOfitsAidList ::= SEQUENCE OF ItsAid
SequenceOfitsAidSspList ::= SEQUENCE OF ItsAidSsp

END

CER DEFINITIONS AUTOMATIC TAGS ::= BEGIN

EXPORTS ALL;
IMPORTS 
    Uint8,
    Signature,
    HashedId8,
    CertificateDigest,
    PublicVerifyKey,
    PublicEncryptionKey,
    SubjectAssurance,
    SequenceOfitsAidList,
    SequenceOfitsAidSspList,
    GeographicRegion,
    Time32 FROM BASE;

Certificate ::= SEQUENCE {
    version			   Uint8,
    issuer         IssuerId,
    tbs            TbsCert,
    signature      Signature
}

IssuerId ::= CHOICE {
    self 					       NULL,
    certificateDigest    CertificateDigest,
    ...
}

TbsCert ::= SEQUENCE { 
    subjectInfo			        SubjectInfo,
    subjectAttributes		    SubjectAttribute,
    validityRestrictions    ValidityRestriction
}

TbsCertList ::= SEQUENCE OF TbsCert


SubjectInfo ::= SEQUENCE {
    subjectType 	SubjectType,
    subjectName 	OCTET STRING (SIZE (0..32))
}

SubjectType ::= ENUMERATED {
    enrollmentCredential,
    authorizationTicket,
    authorizationAuthority,
    enrollmentAuthority,
    rootCa,
    crlSigner,
    pseudonymTicket,
    pseudonymAuthority
}

SubjectAttribute ::= SEQUENCE {
    verificationKey     PublicVerifyKey,
    encryptionKey 	    PublicEncryptionKey OPTIONAL,
    assuranceLevel	SubjectAssurance OPTIONAL,
    itsAidList          SequenceOfitsAidList OPTIONAL,
    itsAidSspList       SequenceOfitsAidSspList OPTIONAL,
    ...
}

ValidityRestriction ::= SEQUENCE {
    validityPeriod      ValidityPeriod,
    region              GeographicRegion OPTIONAL,
    ...
}

ValidityPeriod ::= CHOICE {
    timeEnd             Time32,
    timeStartAndEnd     TimeStartAndEnd
}

TimeStartAndEnd ::= SEQUENCE {
    startValidity       Time32,
    endValidity         Time32
}

SequenceOfCertificate ::= SEQUENCE OF Certificate 

END

SecMsg DEFINITIONS AUTOMATIC TAGS ::= BEGIN
	
EXPORTS ALL;
IMPORTS 
    Uint8,
    Time64,
    Opaque,
    Signature,
    CertificateDigest,
    HashAlgorithm,
    ThreeDLocation,
    HashedId3,
    PublicEncryptionKey,
    HashedId8,
    EccCurve,
    ECCPoint FROM BASE
    SequenceOfCertificate FROM CER;

SecuredMessage ::= SEQUENCE {
    version		Uint8,
    payload		Payload
}

Payload ::= CHOICE {
    unSecuredData    Opaque,
    signedData     	 SignedData,
    encData    		   EncryptedData
}

SignedData ::= SEQUENCE {
    signer    SignerInfo,
    tbs 		  TBSData, 
    sign 		  Signature
}

SignerInfo ::= CHOICE {
    self             		 NULL,
    certificate        	 SequenceOfCertificate,
    certificateDigest    CertificateDigest,
    ...
}

TBSData ::= SEQUENCE {
    headerInfo    HeaderInfo,
    data 			    OCTET STRING (SIZE(0..MAX)) OPTIONAL,
    extHash 		  OCTET STRING (SIZE(32)) OPTIONAL
}

HeaderInfo ::= SEQUENCE {
    itsAid    		INTEGER,
    hashAlg 		  HashAlgorithm OPTIONAL,
    genTime 		  Time64 OPTIONAL,
    expiryTime    Time64 OPTIONAL,
    location 		  ThreeDLocation OPTIONAL,
    digest 			  HashedId3 OPTIONAL,
    encKey 			  PublicEncryptionKey OPTIONAL
}

EncryptedData ::= SEQUENCE {
    recipients   	SequenceOfRecipientInfo,
    cipherText 		SymmetricCipherText
}

RecipientInfo ::= CHOICE{
    pskRecipientInfo    	PreSharedKeyRecipientInfo,
    symmRecipInfo 			  SymmRecipInfo,
    certRecipInfo 			  PKRecipientInfo,
    signedDataRecipInfo 	PKRecipientInfo
}

PreSharedKeyRecipientInfo ::= SEQUENCE {
    hashAlg     	HashAlgorithm,
    symKeyHash 		HashedId8
}

SymmRecipInfo ::= SEQUENCE {
    hashAlg 		  HashAlgorithm,
    recipientId 	HashedId8,
    encKey 			  SymmetricCipherText
}

PKRecipientInfo ::= SEQUENCE {
    hashAlg 		  HashAlgorithm,
    recipientId 	HashedId8,
    kek 			    EciesEncryptedKey
}

EciesEncryptedKey ::= SEQUENCE {
    eccCcurve  	EccCurve,
    v			      ECCPoint,
    c 			    OCTET STRING (SIZE(16)),
    t 			    OCTET STRING (SIZE(32))
}

SymmetricCipherText ::= CHOICE {
    sm4Ecb  	CipherText,
    sm4Cbc 		SM4CipherText,
    sm4Cfb 		SM4CipherText,
    sm4Ofb 		SM4CipherText,
    aesCcm 		AesCcmCipherText
}

CipherText ::= Opaque
SM4CipherText ::= SEQUENCE {
    iv   		  OCTET STRING (SIZE(16)),
    cipher 		CipherText
}

AesCcmCipherText ::= SEQUENCE {
    nonce 		OCTET STRING (SIZE(12)),
    cipher 		CipherText
}

SequenceOfRecipientInfo ::= SEQUENCE OF RecipientInfo

END

EncryptedMessage DEFINITIONS AUTOMATIC TAGS ::= BEGIN

-- imports and exports
IMPORTS	PcertRequestMsg FROM PcertReqMsg
		PcertRespMsg FROM PcertRespMsg
		AcertRequestMsg FROM AcertReqMsg
		AcertRespMsg FROM AcertRespMsg;

-- Main message frame
EncryptedMessage ::= CHOICE { 
	pcertReq PcertRequestMsg,
	pcertRsp PcertRespMsg,
	acertReq AcertRequestMsg,
	acertRsp AcertRespMsg
}
	
END

AcertReqMsg DEFINITIONS AUTOMATIC TAGS ::= BEGIN

IMPORTS Signature FROM CER
    Uint16 FROM BASE
    Time32 FROM BASE
    EciesEncryptedKey FROM SecMsg
    SM4CipherText FROM SecMsg
    Certificate FROM CER
    SequenceOfitsAidList FROM CER
    SequenceOfitsAidSspList FROM CER
    PublicVerifyKey FROM CER;

AcertRequestMsg ::= SEQUENCE {
    signDate AcertReqMsgSig,
    signature Signature
}

AcertReqMsgSig ::= SEQUENCE { --签名原文
    genTime Time32,
    kek EciesEncryptedKey, --对称密钥密文
    encData SM4CipherText, --对称加密密文
    enrollmentCert Certificate
}

AcertRequestMsgBody ::= SEQUENCE { --对称加密原文
    subjectName OCTET STRING (SIZE(0..32)),
    itsAidList SequenceOfitsAidList,
    itsAidSspList SequenceOfitsAidSspList,
    verificationKey PublicVerifyKey
}

END

AcertRespMsg DEFINITIONS AUTOMATIC TAGS ::= BEGIN

IMPORTS Signature FROM CER
    Uint16 FROM BASE
    Time32 FROM BASE
    EciesEncryptedKey FROM SecMsg
    SM4CipherText FROM SecMsg
    Certificate FROM CER;

AcertRespMsg ::= SEQUENCE {
    signDate AcertRespMsgSig,
    signature Signature
}

AcertRespMsgSig ::= SEQUENCE { --签名原文
    genTime Time32,
    kek EciesEncryptedKey, --对称密钥密文
    encData SM4CipherText --对称加密密文
}

AcertRespMsgBody ::= SEQUENCE { --对称加密原文
    applicationCert Certificate
}

END

PcertReqMsg DEFINITIONS AUTOMATIC TAGS ::= BEGIN

IMPORTS Signature FROM CER
    Uint16 FROM BASE
    Time32 FROM BASE
    EciesEncryptedKey FROM SecMsg
    SM4CipherText FROM SecMsg
    Certificate FROM CER
    SequenceOfitsAidList FROM CER
    SequenceOfitsAidSspList FROM CER
    PublicVerifyKey FROM CER;

PcertRequestMsg ::= SEQUENCE {
    signData PcertReqMsgSig,
    signature Signature
}

PcertReqMsgSig ::= SEQUENCE { --签名原文
    genTime Time32,
    kek EciesEncryptedKey, --对称密钥密文
    encData SM4CipherText, --对称加密密文
    enrollmentCert Certificate
}

PcertRequestMsgBody ::= SEQUENCE { --对称加密原文
    subjectName OCTET STRING (SIZE(0..32)),
    itsAidList SequenceOfitsAidList,
    itsAidSspList SequenceOfitsAidSspList,
    verificationKeys PublicVerifyKeyList
}


PublicVerifyKeyList ::= SEQUENCE OF PublicVerifyKey

END

--OBU假名证书响应消息体ASN.1定义

PcertRespMsg DEFINITIONS AUTOMATIC TAGS ::= BEGIN

IMPORTS Signature FROM CER
    Uint8 FROM BASE
    Uint16 FROM BASE
    Time32 FROM BASE
    ECCPoint FROM BASE
    EccCurve FROM BASE
    HashAlgorithm FROM BASE
    EciesEncryptedKey FROM SecMsg
    SM4CipherText FROM SecMsg
    PublicEncryptionKey FROM SecMsg
    Certificate FROM CER
    TbsCertList FROM CER;


PcertRespMsg ::= SEQUENCE {
    signData PcertRespMsgSig,
    signature Signature
}

PcertRespMsgSig ::= SEQUENCE { --签名原文
    genTime Time32,
    kek EciesEncryptedKey, --对称密钥密文
    encData SM4CipherText --对称加密密文
}

PcertRespMsgBody ::= SEQUENCE { --对称加密原文
    pseudonymCerts CertificateList
}

CertificateList ::= SEQUENCE SIZE(1..32) OF Certificate

CertRequest ::= SEQUENCE {
		version  Uint8,
		currentTime Time32,
		tbsCertDataList TbsCertList,
		encryptionKey PublicEncryptionKey OPTIONAL
}

ECDHMessage::= SEQUENCE {
    version Uint8,
    hashAlg HashAlgorithm,
    curve EccCurve,
    dhID  OCTET STRING (SIZE(16)),
    dhStartTime Time32 OPTIONAL,
    dhExpireTime Time32 OPTIONAL,
    dhData ECDHContent
}

ECDHContent::= CHOICE {
    exchangeData ECDHData,
    exchangeConfirm ECDHConfirm,
    exchangeResult ECDHResult,
    ...
}

ECDHData ::= SEQUENCE {
    keyStartTime Time32,
    keyExpireTime Time32,
    dhKey ECCPoint,
    ...
}

ECDHConfirm ::= SEQUENCE {
    confirmDataS OCTET STRING (SIZE(32)),
    ...
}

ECDHResult ::= SEQUENCE {
    result DHResult,
    ...
}

DHResult ::= ENUMERATED{
    success,
    refuse,
    stateError,
    timeOut,
    ...
}

END
